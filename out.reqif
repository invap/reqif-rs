# Requirements examples

# Specification: Crypto Ar User Requirements

## CAUR-1: Titulo del requerimiento 1
Texto del requerimiento 1.

## CAUR-2: Titulo del requerimiento 2
Texto del requerimiento 2sdlfkj
